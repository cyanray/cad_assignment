Attribute VB_Name = "AcadBlockProxy"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Private m_Block As AcadBlock

Public Property Set Block(ByRef BlockRef As AcadBlock)
    Set m_Block = BlockRef
End Property

Public Function AddLine(StartPoint As Point3, EndPoint As Point3, Optional LayerName As String = "0")
    Set AddLine = m_Block.AddLine(StartPoint.ToArray(), EndPoint.ToArray())
    AddLine.Layer = LayerName
End Function

Public Function AddLineXYZXYZ(x1 As Double, y1 As Double, z1 As Double, x2 As Double, y2 As Double, z2 As Double, Optional LayerName As String = "0")
    Dim pt1 As New Point3
    Dim pt2 As New Point3
    pt1.XYZ x1, y1, z1
    pt2.XYZ x2, y2, z2
    Set AddLineXYZXYZ = AddLine(pt1, pt2)
    AddLineXYZXYZ.Layer = LayerName
End Function

Public Function AddSpline(Points As Point3Collection, StartTangent As Point3, EndTangent As Point3, Optional LayerName As String = "0")
    Set AddSpline = m_Block.AddSpline(Points.ToArray(), StartTangent.ToArray(), EndTangent.ToArray())
    AddSpline.Layer = LayerName
End Function

Public Function AddText(Content As String, InsertionPoint As Point3, Height As Double, Optional Alignment As AcAlignment = acAlignmentLeft, Optional LayerName As String = "0")
    Set AddText = m_Block.AddText(Content, InsertionPoint.ToArray(), Height)
    AddText.Layer = LayerName
    AddText.Alignment = Alignment
    If Alignment <> acAlignmentLeft Then
        AddText.TextAlignmentPoint = InsertionPoint.ToArray()
    End If
End Function

Attribute VB_Name = "CurveSpline"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public Points As Point3Collection
Public Argument As Variant

Private Sub Class_Initialize()
    Set Points = New Point3Collection
End Sub

Public Sub Add(ByVal point As Point3)
    Points.Add point
End Sub

Public Sub AddXYZ(ByVal X As Double, ByVal Y As Double, ByVal Z As Double)
    Points.AddXYZ X, Y, Z
End Sub

Public Sub Reverse()
    Points.Reverse
End Sub

Attribute VB_Name = "DataLoader"
Option Explicit

Function ReadDataFromTxtFile(FilePath As String, Optional NumericScale As Double = 1#) As ShipOffsets
    Dim result As New ShipOffsets
    
    ' TODO: Determine from file
    Const MaxRow As Integer = 14
    Const MaxCol As Integer = 29

    Dim matrix(1 To MaxRow, 1 To MaxCol) As Double
    
    ' Read matrix from file
    Open FilePath For Input As #1
    Dim i As Integer, j As Integer
    For i = 1 To MaxRow
        Dim line As String
        Line Input #1, line
        Dim numbers() As String
        numbers = Split(line, " ")
        For j = 1 To MaxCol
            matrix(i, j) = CDbl(numbers(j - 1))
            If Not i = 1 And Not matrix(i, j) = GInvalidValue Then
                matrix(i, j) = matrix(i, j) * NumericScale
            End If
        Next j
    Next i
    Close #1

    ' Print matrix
    For i = 1 To MaxRow
        For j = 1 To MaxCol
            Debug.Print matrix(i, j);
        Next j
        Debug.Print
    Next i

    ' The first and last line are station data
    For i = 1 To MaxCol
        If matrix(1, i) = GInvalidValue Or matrix(MaxRow, i) = GInvalidValue Then
            GoTo ContinueLoop
        End If

        result.AddStationByValue matrix(1, i), matrix(MaxRow, i)
ContinueLoop:
    Next i

    ' The first column are water planes
    For i = 2 To MaxRow
        If matrix(i, 1) = GInvalidValue Then
            GoTo ContinueLoop1
        End If
        result.AddWaterPlane matrix(i, 1)
ContinueLoop1:
    Next i

    ' Parsing waterlines
    For i = 2 To MaxRow - 2
        Dim wl As CurveSpline
        Set wl = New CurveSpline
        wl.Argument = matrix(i, 1)
        If Not matrix(i, 2) = GInvalidValue Then
            wl.AddXYZ matrix(i, 2), 0, 0
        End If

        For j = 3 To MaxCol - 1
            If matrix(i, j) = GInvalidValue Then
                GoTo ContinueLoop2
            End If
            wl.AddXYZ matrix(MaxRow, j), matrix(i, j), 0
ContinueLoop2:
        Next j

        If Not matrix(i, MaxCol) = GInvalidValue Then
            wl.AddXYZ matrix(i, MaxCol), 0, 0
        End If
        result.AddWaterLine wl
    Next i

    ' Parsing SheerLines
    Dim sl As CurveSpline: Set sl = New CurveSpline
    For j = 2 To MaxCol - 1
        If matrix(MaxRow - 1, j) <> GInvalidValue Then
            sl.AddXYZ matrix(MaxRow, j), matrix(MaxRow - 1, j), 0
        End If
    Next j
    result.AddSheerLine sl
    
    ' Work done.
    Set ReadDataFromTxtFile = result
End Function

Sub GenerateSheerLinesFromWaterLines(ByRef offset As ShipOffsets)
    ReDim result(1 To offset.SheerPlanes.Count) As CurveSpline
    Dim i As Integer
    For i = LBound(result) To UBound(result)
        Set result(i) = New CurveSpline
    Next i

    IntersectWithWaterLines offset, result, False

    Dim Item
    For Each Item In result
        Item.Reverse
    Next Item

    IntersectWithWaterLines offset, result, True

    For i = LBound(result) To UBound(result)
        offset.AddSheerLine result(i)
    Next i

End Sub

Sub IntersectWithWaterLines(ByRef offset As ShipOffsets, ByRef result() As CurveSpline, Flag As Boolean)
    Dim IdxWaterLine As Integer
    Dim IdxSheerPlane As Integer
    Dim tempBlock As AcadBlock
    Set tempBlock = ThisDrawing.Blocks.Add(GOrigin.ToArray(), GBlockName_Temp)
    Dim tempProxy As New AcadBlockProxy: Set tempProxy.Block = tempBlock
        For IdxWaterLine = 1 To offset.WaterLines.Count
        Dim wl As AcadSpline
        Set wl = tempProxy.AddSpline(offset.WaterLines(IdxWaterLine).Points, GOrigin, GOrigin)
        For IdxSheerPlane = 1 To offset.SheerPlanes.Count
            Dim sp As AcadLine
            If Flag Then
                Set sp = tempProxy.AddLineXYZXYZ(0, offset.SheerPlanes(IdxSheerPlane), 0, GInf, offset.SheerPlanes(IdxSheerPlane), 0)
            Else
                Set sp = tempProxy.AddLineXYZXYZ(-GInf, offset.SheerPlanes(IdxSheerPlane), 0, 0, offset.SheerPlanes(IdxSheerPlane), 0)
            End If
            Dim pointsArray
            pointsArray = sp.IntersectWith(wl, acExtendNone)
            Dim Points As Point3Collection: Set Points = New Point3Collection
            Points.AddFromArray pointsArray
            If Points.Count = 1 And offset.WaterLines(IdxWaterLine).Argument <> GInvalidValue Then
                result(IdxSheerPlane).AddXYZ Points.Item(1).X, offset.WaterLines(IdxWaterLine).Argument, 0
            End If
            sp.Delete
        Next IdxSheerPlane
        wl.Delete
    Next IdxWaterLine
    tempBlock.Delete
End Sub

Sub GenerateBodyLinesFromWaterLines(ByRef offset As ShipOffsets, ByRef stationLines As Collection)
    Dim i As Integer
    Dim tempBlock As AcadBlock
    Set tempBlock = ThisDrawing.Blocks.Add(GOrigin.ToArray(), GBlockName_Temp)
    Dim tempProxy As New AcadBlockProxy: Set tempProxy.Block = tempBlock

    For i = 1 To stationLines.Count
        Dim sp As AcadLine
        Set sp = tempProxy.AddLineXYZXYZ(stationLines(i) + 0.0001, -GInf, 0, stationLines(i) + 0.0001, GInf, 0)
        Dim j As Integer
        Dim bl As CurveSpline
        Set bl = New CurveSpline
        For j = 1 To offset.WaterLines.Count
            Dim wl As AcadSpline
            Set wl = tempProxy.AddSpline(offset.WaterLines(j).Points, GOrigin, GOrigin)
            Dim pointsArray
            pointsArray = sp.IntersectWith(wl, acExtendNone)
            Dim Points As Point3Collection: Set Points = New Point3Collection
            Points.AddFromArray pointsArray
            If Points.Count = 1 And offset.WaterLines(j).Argument <> GInvalidValue Then
                Dim xval As Double: xval = Points.Item(1).Y
                If stationLines(i) < 0 Then
                    xval = -xval
                End If
                If offset.WaterLines(j).Argument = 0 Then
                    Dim step As Double: step = xval / 8
                    Dim t As Integer
                    For t = 8 To 1 Step -1
                        bl.AddXYZ xval - step * t, 0, 0
                    Next t
                End If
                bl.AddXYZ xval, offset.WaterLines(j).Argument, 0
            End If
            wl.Delete
        Next j
        If bl.Points.Count >= 2 Then
            offset.AddBodyLine bl
        End If
        sp.Delete
    Next i
    tempBlock.Delete
End Sub

Attribute VB_Name = "Point3"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public X As Double, Y As Double, Z As Double

Public Sub XYZ(xval As Double, yval As Double, zval As Double)
X = xval: Y = yval: Z = zval
End Sub

Public Function ToArray() As Double()
    Dim result(2) As Double
    result(0) = X: result(1) = Y: result(2) = Z
    ToArray = result
End Function

Attribute VB_Name = "Point3Collection"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Private m_Collection As Collection

Private Sub Class_Initialize()
    Set m_Collection = New Collection
End Sub

Public Sub Add(point As Point3)
    m_Collection.Add point
End Sub

Public Sub AddXYZ(X As Double, Y As Double, Z As Double)
    Dim point As New Point3
    point.XYZ X, Y, Z
    Add point
End Sub

Public Sub AddFromArray(arr As Variant)
    Dim Idx As Integer
    Dim point As Point3
    For Idx = 0 To UBound(arr) Step 3
        Call AddXYZ((arr(Idx + 0)), (arr(Idx + 1)), (arr(Idx + 2)))
    Next
End Sub

Public Function Count() As Integer
    Count = m_Collection.Count
End Function

Public Function Item(index As Integer) As Point3
    Set Item = m_Collection.Item(index)
End Function

Public Function ToArray() As Double()
    Dim UpperBnd As Integer
    UpperBnd = 3 * m_Collection.Count - 1
    ReDim result(UpperBnd) As Double
    Dim Idx As Integer
    Dim point As Point3
    For Idx = 1 To m_Collection.Count
        Set point = m_Collection.Item(Idx)
        result((Idx - 1) * 3 + 0) = point.X
        result((Idx - 1) * 3 + 1) = point.Y
        result((Idx - 1) * 3 + 2) = point.Z
    Next
    ToArray = result
End Function

Public Sub Reverse()
    Dim NewCol As Collection
    Set NewCol = New Collection
    Dim obj
    For Each obj In m_Collection
        If NewCol.Count > 0 Then
            NewCol.Add Item:=obj, before:=1
        Else
            NewCol.Add Item:=obj
        End If
    Next
    Set m_Collection = NewCol
End Sub

Attribute VB_Name = "ShipOffsets"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

' ElementType: CurveSpline
Private m_WaterLines As Collection
' ElementType: CurveSpline
Private m_SheerLines As Collection
' ElementType: CurveSpline
Private m_BodyLines As Collection

' ElementType: Station
Private m_Stations As Collection
' ElementType: Double
Private m_WaterPlane As Collection
' ElementType: Double
Private m_SheerPlane As Collection

Private m_Breadth As Double

Private m_Depth As Double

Private m_HorizontalPadding As Double

Private m_TextHeight As Double

Private Sub Class_Initialize()
    Set m_WaterLines = New Collection
    Set m_SheerLines = New Collection
    Set m_BodyLines = New Collection
    Set m_Stations = New Collection
    Set m_WaterPlane = New Collection
    Set m_SheerPlane = New Collection
    m_Breadth = GInvalidValue
    m_Depth = GInvalidValue
    HorizontalPadding = 0
End Sub

Private Property Get HorizontalLineLeft() As Double
    HorizontalLineLeft = m_Stations(1).StationOffset - m_HorizontalPadding
End Property

Private Property Get HorizontalLineRight() As Double
    HorizontalLineRight = m_Stations(m_Stations.Count).StationOffset + m_HorizontalPadding
End Property

Public Property Get HalfBreadth() As Double
    HalfBreadth = m_Breadth / 2
End Property

Public Property Get Breadth() As Double
    Breadth = m_Breadth
End Property

Public Property Let Breadth(ByVal Value As Double)
    m_Breadth = Value
End Property

Public Property Get Depth() As Double
    Depth = m_Depth
End Property

Public Property Let Depth(ByVal Value As Double)
    m_Depth = Value
End Property

Public Property Get HorizontalPadding() As Double
    HorizontalPadding = m_HorizontalPadding
End Property

Public Property Let HorizontalPadding(ByVal Value As Double)
    m_HorizontalPadding = Value
End Property

Public Property Get TextHeight() As Double
    TextHeight = m_TextHeight
End Property

Public Property Let TextHeight(ByVal Value As Double)
    m_TextHeight = Value
End Property

Public Property Get WaterLines() As Collection
    Set WaterLines = m_WaterLines
End Property

Public Property Get SheerLines() As Collection
    Set SheerLines = m_SheerLines
End Property

Public Property Get BodyLines() As Collection
    Set BodyLines = m_BodyLines
End Property

Public Property Get SheerPlanes() As Collection
    Set SheerPlanes = m_SheerPlane
End Property

Public Property Get Stations() As Collection
    Dim result As Collection
    Set result = New Collection
    Dim i As Integer
    For i = 1 To m_Stations.Count
        result.Add m_Stations(i).StationOffset
    Next i
    Set Stations = result
End Property

Public Sub AddWaterLine(wl As CurveSpline)
    m_WaterLines.Add wl
End Sub

Public Sub AddSheerLine(sl As CurveSpline)
    m_SheerLines.Add sl
End Sub

Public Sub AddBodyLine(bl As CurveSpline)
    m_BodyLines.Add bl
End Sub

Public Sub AddStation(sta As Station)
    ' TODO: Ensure the elements are sorted.
    m_Stations.Add sta
End Sub

Public Sub AddStationByValue(staNumber As Double, staOffset As Double)
    ' TODO: Ensure the elements are sorted.
    Dim sta As New Station
    sta.StationNumber = staNumber
    sta.StationOffset = staOffset
    AddStation sta
End Sub

Public Sub AddWaterPlane(sheerPlane As Double)
    ' TODO: Ensure the elements are sorted.
    m_WaterPlane.Add sheerPlane
End Sub

Public Sub AddSheerPlane(sheerPlane As Double)
    ' TODO: Ensure the elements are sorted.
    m_SheerPlane.Add sheerPlane
End Sub

Public Sub DrawHalfBreadthPlanWaterLine(BlockProxy As AcadBlockProxy, Optional LayerName As String = "0")
    Dim i As Integer
    For i = 1 To m_WaterLines.Count
        BlockProxy.AddSpline m_WaterLines(i).Points, GOrigin, GOrigin, LayerName
    Next i
End Sub

Public Sub DrawHalfBreadthPlanGrid(BlockProxy As AcadBlockProxy, Optional LayerName As String = "0")
    ' Throw exception if m_Breadth invalid
    If m_Breadth = GInvalidValue Then
        Err.Raise 10001, "ShipOffsets", "m_Breadth is invalid."
    End If

    Dim leftOffset As Double
    Dim rightOffset As Double
    leftOffset = m_Stations(1).StationOffset
    rightOffset = m_Stations(m_Stations.Count).StationOffset
    Dim startLength As Double: startLength = leftOffset - m_HorizontalPadding
    Dim endLength As Double: endLength = rightOffset + m_HorizontalPadding

    Dim i As Integer
    For i = 1 To m_Stations.Count
        Dim sta As Station: Set sta = m_Stations(i)
        BlockProxy.AddLineXYZXYZ sta.StationOffset, 0, 0, sta.StationOffset, HalfBreadth, 0, LayerName
    Next i
    For i = 1 To m_SheerPlane.Count
        Dim sheerPlane As Double: sheerPlane = m_SheerPlane(i)
        If sheerPlane = 0 Or sheerPlane = HalfBreadth Then
            GoTo ContinueLoop
        End If
        BlockProxy.AddLineXYZXYZ startLength, sheerPlane, 0, endLength, sheerPlane, 0, LayerName
ContinueLoop:
    Next i
    ' BaseLine
    BlockProxy.AddLineXYZXYZ startLength, 0, 0, endLength, 0, 0, LayerName
    ' TopLine
    BlockProxy.AddLineXYZXYZ startLength, HalfBreadth, 0, endLength, HalfBreadth, 0, LayerName
End Sub

Public Sub DrawSheerPlanSheerLine(BlockProxy As AcadBlockProxy, Optional LayerName As String = "0")
    Dim i As Integer
    For i = 1 To m_SheerLines.Count
        Dim ln As AcadSpline
        ' Patch for parallel middle body
        Dim slOrigin As CurveSpline: Set slOrigin = m_SheerLines(i)
        ' Find the index of point that Y = 0
        Dim Idx As Integer
        For Idx = 1 To slOrigin.Points.Count
            Dim pt As Point3: Set pt = slOrigin.Points.Item(Idx)
            If pt.Y = 0 Then
                Exit For
            End If
        Next Idx
        ' If found
        If Idx < slOrigin.Points.Count Then
            Dim x1 As Double: x1 = slOrigin.Points.Item(Idx).X
            Dim x2 As Double: x2 = slOrigin.Points.Item(Idx + 1).X
            Dim step As Double: step = (x2 - x1) / 16
            Dim sl As CurveSpline: Set sl = New CurveSpline
            Dim j As Integer
            For j = 1 To Idx
                sl.Add slOrigin.Points.Item(j)
            Next j
            For j = 1 To 16
                sl.AddXYZ x1 + j * step, 0, 0
            Next j
            For j = Idx + 1 To slOrigin.Points.Count
                sl.Add slOrigin.Points.Item(j)
            Next j
            Set ln = BlockProxy.AddSpline(sl.Points, GOrigin, GOrigin)
        Else
            Set ln = BlockProxy.AddSpline(slOrigin.Points, GOrigin, GOrigin)
        End If
        ln.Layer = LayerName
    Next i
End Sub

Public Sub DrawSheerPlanGrid(BlockProxy As AcadBlockProxy, Optional LayerName As String = "0")
    ' Throw exception if m_Depth invalid
    If m_Depth = GInvalidValue Then
        Err.Raise 10001, "ShipOffsets", "m_Depth is invalid."
    End If

    Dim leftOffset As Double
    Dim rightOffset As Double
    leftOffset = m_Stations(1).StationOffset
    rightOffset = m_Stations(m_Stations.Count).StationOffset
    Dim startLength As Double: startLength = leftOffset - m_HorizontalPadding
    Dim endLength As Double: endLength = rightOffset + m_HorizontalPadding

    Dim i As Integer
    For i = 1 To m_Stations.Count
        Dim sta As Station: Set sta = m_Stations(i)
        BlockProxy.AddLineXYZXYZ sta.StationOffset, 0, 0, sta.StationOffset, m_Depth, 0, LayerName
    Next i
    For i = 1 To m_WaterPlane.Count
        Dim waterPlane As Double: waterPlane = m_WaterPlane(i)
        If waterPlane = 0 Or waterPlane = m_Depth Then
            GoTo ContinueLoop
        End If
        BlockProxy.AddLineXYZXYZ startLength, waterPlane, 0, endLength, waterPlane, 0, LayerName
ContinueLoop:
    Next i
    ' BaseLine
    BlockProxy.AddLineXYZXYZ startLength, 0, 0, endLength, 0, 0, LayerName
    ' TopLine
    BlockProxy.AddLineXYZXYZ startLength, m_Depth, 0, endLength, m_Depth, 0, LayerName
End Sub

Public Sub DrawBodyPlanBodyLine(BlockProxy As AcadBlockProxy, Optional LayerName As String = "0")
    Dim i As Integer
    For i = 1 To m_BodyLines.Count
        BlockProxy.AddSpline m_BodyLines(i).Points, GOrigin, GOrigin, LayerName
    Next i
End Sub

Public Sub DrawBodyPlanGrid(BlockProxy As AcadBlockProxy, Optional LayerName As String = "0")
    ' Throw exception if m_Depth or m_Breadth invalid
    If m_Depth = GInvalidValue Then
        Err.Raise 10001, "ShipOffsets", "m_Depth is invalid."
    End If
    If m_Breadth = GInvalidValue Then
        Err.Raise 10001, "ShipOffsets", "m_Breadth is invalid."
    End If

    Dim leftOffset As Double
    Dim rightOffset As Double
    leftOffset = -HalfBreadth - m_HorizontalPadding
    rightOffset = HalfBreadth + m_HorizontalPadding

    ' draw water plane and sheer plane
    Dim i As Integer
    For i = 1 To m_WaterPlane.Count
        Dim waterPlane As Double: waterPlane = m_WaterPlane(i)
        BlockProxy.AddLineXYZXYZ leftOffset, waterPlane, 0, rightOffset, waterPlane, 0, LayerName
    Next i
    For i = 1 To m_SheerPlane.Count
        Dim sheerPlane As Double: sheerPlane = m_SheerPlane(i)
        BlockProxy.AddLineXYZXYZ sheerPlane, 0, 0, sheerPlane, Depth, 0, LayerName
        BlockProxy.AddLineXYZXYZ -sheerPlane, 0, 0, -sheerPlane, Depth, 0, LayerName
    Next i
    ' BaseLine
    BlockProxy.AddLineXYZXYZ leftOffset, 0, 0, rightOffset, 0, 0, LayerName
    BlockProxy.AddLineXYZXYZ 0, 0, 0, 0, Depth, 0, LayerName
    ' blockProxy.AddLineXYZXYZ -HalfBreadth, Depth, 0, HalfBreadth, Depth, 0, LayerName
    BlockProxy.AddLineXYZXYZ -HalfBreadth, 0, 0, -HalfBreadth, Depth, 0, LayerName
    BlockProxy.AddLineXYZXYZ HalfBreadth, 0, 0, HalfBreadth, Depth, 0, LayerName
End Sub

Public Sub DrawHalfBreadthPlanText(BlockProxy As AcadBlockProxy, Optional LayerName As String = "0")
    Dim pt As Point3
    Dim i As Integer
    For i = 1 To m_Stations.Count
        Dim sta As Station: Set sta = m_Stations(i)
        Set pt = New Point3
        pt.XYZ sta.StationOffset, 0, 0
        BlockProxy.AddText CStr(Abs(sta.StationNumber)), pt, TextHeight, acAlignmentTopCenter, LayerName
    Next i
    For i = 1 To m_SheerPlane.Count
        Dim sheerPlane As Double: sheerPlane = m_SheerPlane(i)
        ' skip sheer plane at 0
        If sheerPlane = 0 Then
            GoTo ContinueLoop
        End If
        Set pt = New Point3
        pt.XYZ HorizontalLineLeft, sheerPlane, 0
        BlockProxy.AddText CStr(Abs(sheerPlane)) & "BL", pt, TextHeight, acAlignmentLeft, LayerName
        pt.XYZ HorizontalLineRight, sheerPlane, 0
        BlockProxy.AddText CStr(Abs(sheerPlane)) & "BL", pt, TextHeight, acAlignmentRight, LayerName
ContinueLoop:
    Next i
    'Base line
    pt.XYZ HorizontalLineLeft, 0, 0
    BlockProxy.AddText "BL", pt, TextHeight, acAlignmentLeft, LayerName
    pt.XYZ HorizontalLineRight, 0, 0
    BlockProxy.AddText "BL", pt, TextHeight, acAlignmentRight, LayerName
End Sub

Public Sub DrawSheerPlanText(BlockProxy As AcadBlockProxy, Optional LayerName As String = "0")
    Dim pt As Point3
    Dim i As Integer
    For i = 1 To m_Stations.Count
        Dim sta As Station: Set sta = m_Stations(i)
        Set pt = New Point3
        pt.XYZ sta.StationOffset, 0, 0
        BlockProxy.AddText CStr(Abs(sta.StationNumber)), pt, TextHeight, acAlignmentTopCenter, LayerName
    Next i
    For i = 1 To m_WaterPlane.Count
        Dim waterPlane As Double: waterPlane = m_WaterPlane(i)
        ' skip water plane = 0
        If waterPlane = 0 Then
            GoTo ContinueLoop
        End If
        Set pt = New Point3
        pt.XYZ HorizontalLineLeft, waterPlane, 0
        BlockProxy.AddText CStr(Abs(waterPlane)) & "WL", pt, TextHeight, acAlignmentLeft, LayerName
        pt.XYZ HorizontalLineRight, waterPlane, 0
        BlockProxy.AddText CStr(Abs(waterPlane)) & "WL", pt, TextHeight, acAlignmentRight, LayerName
ContinueLoop:
    Next i
    'Base line
    pt.XYZ HorizontalLineLeft, 0, 0
    BlockProxy.AddText "BL", pt, TextHeight, acAlignmentLeft, LayerName
    pt.XYZ HorizontalLineRight, 0, 0
    BlockProxy.AddText "BL", pt, TextHeight, acAlignmentRight, LayerName
End Sub

Public Sub DrawBodyPlanText(BlockProxy As AcadBlockProxy, Optional LayerName As String = "0")
    Dim pt As Point3
    Dim i As Integer

    Dim leftOffset As Double: leftOffset = -HalfBreadth - m_HorizontalPadding
    Dim rightOffset As Double: rightOffset = HalfBreadth + m_HorizontalPadding

    For i = 1 To m_SheerPlane.Count
        Dim sheerPlane As Double: sheerPlane = m_SheerPlane(i)
        ' skip sheer plane at 0
        If sheerPlane = 0 Then
            GoTo ContinueLoop1
        End If
        Set pt = New Point3
        pt.XYZ sheerPlane, 0, 0
        BlockProxy.AddText CStr(Abs(sheerPlane)), pt, TextHeight, acAlignmentTopCenter, LayerName
        pt.XYZ -sheerPlane, 0, 0
        BlockProxy.AddText CStr(Abs(sheerPlane)), pt, TextHeight, acAlignmentTopCenter, LayerName
ContinueLoop1:
    Next i

    For i = 1 To m_WaterPlane.Count
        Dim waterPlane As Double: waterPlane = m_WaterPlane(i)
        ' skip water plane = 0
        If waterPlane = 0 Then
            GoTo ContinueLoop2
        End If
        Set pt = New Point3
        pt.XYZ leftOffset, waterPlane, 0
        BlockProxy.AddText CStr(Abs(waterPlane)) & "WL", pt, TextHeight, acAlignmentLeft, LayerName
        pt.XYZ rightOffset, waterPlane, 0
        BlockProxy.AddText CStr(Abs(waterPlane)) & "WL", pt, TextHeight, acAlignmentRight, LayerName
ContinueLoop2:
    Next i
    ' Base line
    pt.XYZ 0, 0, 0
    BlockProxy.AddText "CL", pt, TextHeight, acAlignmentTopCenter, LayerName
    pt.XYZ leftOffset, 0, 0
    BlockProxy.AddText "BL", pt, TextHeight, acAlignmentLeft, LayerName
    pt.XYZ rightOffset, 0, 0
    BlockProxy.AddText "BL", pt, TextHeight, acAlignmentRight, LayerName
End Sub

Attribute VB_Name = "Station"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Public StationNumber As Double
Public StationOffset As Double

Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
Sub Main()
    ThisDrawing.PurgeAll ' !!!Warning: FOR DEBUG!!!
    InitProgram "Program Start"
    
    ' TODO: Configurable from file
    Dim FilePath As String
    FilePath = "E:\test\ShipOFF.txt"
    Dim NumericScale As Double
    NumericScale = 1000
    
    Dim ShipOff As ShipOffsets
    Set ShipOff = ReadDataFromTxtFile(FilePath, NumericScale)
    
    ShipOff.AddSheerPlane 3000
    ShipOff.AddSheerPlane 6000
    ShipOff.AddSheerPlane 9000
    ShipOff.AddSheerPlane 12000
    ShipOff.AddSheerPlane 15000
    
    ShipOff.Breadth = 34000
    ShipOff.Depth = 19000
    ShipOff.HorizontalPadding = 9000
    ShipOff.TextHeight = 700
    
    Call GenerateSheerLinesFromWaterLines(ShipOff)
    Call GenerateBodyLinesFromWaterLines(ShipOff, ShipOff.Stations)
    
    Dim pt As Point3: Set pt = New Point3
    Dim proxy As AcadBlockProxy
    
    Set proxy = DrawingArea_Create(GBlockName_Temp)
        pt.XYZ 0, 0, 0
        ShipOff.DrawHalfBreadthPlanGrid proxy, GLayerName_Grid
        ShipOff.DrawHalfBreadthPlanWaterLine proxy, GLayerName_HalfBreadthPlan
        ShipOff.DrawHalfBreadthPlanText proxy, GLayerName_Text
    Call DrawingArea_DrawAndClean(GBlockName_Temp, pt)

    Set proxy = DrawingArea_Create(GBlockName_Temp)
        pt.XYZ 0, 30000, 0
        ShipOff.DrawSheerPlanGrid proxy, GLayerName_Grid
        ShipOff.DrawSheerPlanSheerLine proxy, GLayerName_SheerPlan
        ShipOff.DrawSheerPlanText proxy, GLayerName_Text
    Call DrawingArea_DrawAndClean(GBlockName_Temp, pt)

    Set proxy = DrawingArea_Create(GBlockName_Temp)
        pt.XYZ 0, 60000, 0
        ShipOff.DrawBodyPlanGrid proxy, GLayerName_Grid
        ShipOff.DrawBodyPlanBodyLine proxy, GLayerName_BodyPlan
        ShipOff.DrawBodyPlanText proxy, GLayerName_Text
    Call DrawingArea_DrawAndClean(GBlockName_Temp, pt)

End Sub

Attribute VB_Name = "Utils"
Option Explicit

'''' Global Variables ''''
' GOrigin represents the origin (X,Y,Z = 0,0,0)
Public GOrigin As Point3
' GDrawing represents ThisDrawing.ModelSpace
Public GDrawing As New AcadBlockProxy
' GInvalidValue represents an invalid value
Public Const GInvalidValue As Double = -1
' GInf represents infinity value
Public Const GInf As Double = 655350

Public Const GBlockName_Temp As String = "LZY_Lamour_Est_Bleu__"
Public Const GLayerName_Grid As String = "LZY_Grid"
Public Const GLayerName_Text As String = "LZY_Text"
Public Const GLayerName_HalfBreadthPlan As String = "LZY_HalfBreadthPlan"
Public Const GLayerName_SheerPlan As String = "LZY_SheerPlan"
Public Const GLayerName_BodyPlan As String = "LZY_BodyPlan"

' HelloMessage is to avoid this subroutine appearing in the execution panel
Sub InitProgram(HelloMessage As String)
    Debug.Print HelloMessage
    ' Initializes Global Variables
    Set GDrawing.Block = ThisDrawing.ModelSpace
    Set GOrigin = New Point3
    ' This program needs to create some blocks.
    ' Check if the reserved block name exists.
    BlockExists GBlockName_Temp
    ' Create layers
    CreateLayer GLayerName_Grid, acWhite
    CreateLayer GLayerName_Text, acWhite
    CreateLayer GLayerName_HalfBreadthPlan, acCyan
    CreateLayer GLayerName_SheerPlan, acRed
    CreateLayer GLayerName_BodyPlan, acMagenta
End Sub


Sub BlockExists(BlockName As String)
    Dim Exists As Boolean
    Exists = False
    On Error Resume Next
        Dim Blk As AcadBlock
        Set Blk = ThisDrawing.Blocks(BlockName)
        Exists = Not Blk Is Nothing
    On Error GoTo 0
    If Exists Then
        Err.Raise 20001, "Utils", "Block '" & BlockName & "' is exists."
    End If
End Sub

Sub CreateLayer(LayerName As String, Color As AcColor)
    Dim Layer As AcadLayer
    Set Layer = ThisDrawing.Layers.Add(LayerName)
    Layer.Color = Color
End Sub

Function DrawingArea_Create(BlockName As String) As AcadBlockProxy
    Dim Block As AcadBlock
    Set Block = ThisDrawing.Blocks.Add(GOrigin.ToArray(), BlockName)
    Dim BlockProxy As New AcadBlockProxy
    Set BlockProxy.Block = Block
    Set DrawingArea_Create = BlockProxy
End Function

Sub DrawingArea_DrawAndClean(BlockName As String, InsertPoint As Point3)
    Dim Ref As AcadBlockReference
    Set Ref = ThisDrawing.ModelSpace.InsertBlock(InsertPoint.ToArray(), BlockName, 1, 1, 1, 0)
    Ref.Explode
    Ref.Delete
    Dim Block As AcadBlock
    Set Block = ThisDrawing.Blocks(BlockName)
    Block.Delete
End Sub
